FME workspace 1-shp_filtro_rr.fmw
Title: Solutialtech - FME & Sharepoint
History: 14/12/2024,Thiago Brigagão,Criação do Workspace

Parameters:
- SourceDataset_SHAPEFILE = D:\gitHub\SolutialTech\2024\12\sharepoint-fme\1-dataset\BR_Municipios_2022\BR_Municipios_2022.shp   # Source Esri Shapefile(s)

Readers:
- SHAPEFILE_1: SHAPEFILE from $(SourceDataset_SHAPEFILE)

Bookmark: 1.1 | Leitura SHP de Municípios
Note: General Parameters: / Reader Type: Esri Shapefile / Shapefile Name: BR_Municipios_2022 / Reader: BR_Municipios_2022 [SHAPEFILE] / Allowed Geometries: shapefile_polygon / Exposed Attributes: NameTypeCD_MUNvarchar(7)NM_MUNvarchar(50)SIGLA_UFvarchar(2)AREA_KM2double
BR_Municipios_2022 (reader SHAPEFILE_1)
    attributes: CD_MUN varchar(7), NM_MUN varchar(50), SIGLA_UF varchar(2), AREA_KM2 double
    -> Tester

Bookmark: 2.1 | Filtragem da UF RR
Note: SIGLA_UF = SP
Tester
    BOOL_OP = OR
    TEST_CLAUSE = TEST @Value(SIGLA_UF) = RR
    TEST_MODE = TEST
    PASSED -> AttributeCopier

Bookmark: 2.2 | Copia de Atributo
Note: Copia o arquivo para não sobrepor os valores
AttributeCopier
    ATTR_TABLE = COPY NM_MUN > filename
    MISSING_INPUT_ATTRS = REMOVE
    -> StringDiacriticRemover

Bookmark: 2.3 | Remove Acentos
Note: Remove acentuação do atributo selecionado
StringDiacriticRemover
    MOD_ATTRS = filename
    -> StringReplacer_2

Bookmark: 2.4 | Tratamento do Texto
Note: Substitui ' por <nada>
StringReplacer_2
    CASE = NO
    FIND_TEXT = '
    NO_MATCH = _FME_NO_OP_
    REGEXP = NO
    SRC_ATTRS = filename
    -> StringReplacer
Note: Substitui <espaço> por _
StringReplacer
    CASE = NO
    FIND_TEXT = " "
    NO_MATCH = _FME_NO_OP_
    REGEXP = NO
    REPLACE_TEXT = _
    SRC_ATTRS = filename
    -> StringCaseChanger
Note: Passa o case para lowercase
StringCaseChanger
    ATTRCHOICE = SELECTED
    ATTRLIST = filename
    CHANGE_TYPE = lower
    -> FeatureWriter [BR_Municipios_2022]

Bookmark: 1.2| Gravação SHP
Note: Gravação dos arquivos shapefiles separados por municípios
FeatureWriter
    DATASET = D:\gitHub\SolutialTech\2024\12\sharepoint-fme\1-dataset\shp_estado_municipio\@Value(SIGLA_UF)\@Value(filename).zip
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
