FME workspace 2-sharepointonlineconnector-fme.fmw

Parameters:
- SourceDataset_PATH = D:\gitHub\SolutialTech\2024\12\sharepoint-fme\1-dataset\shp_estado_municipio\RR   # INCLUDE_WEB_BROWSER Source Folder and File Pathnames Folder

Readers:
- PATH_1: PATH from $(SourceDataset_PATH)

Bookmark: 1.1 | Leitura dos Arquivos
Note: Leitura de Diretório com os arquivos compactados
PATH (reader PATH_1)
    attributes: path_unix buffer, path_windows buffer, path_rootname buffer, path_filename buffer, path_extension buffer, path_directory_unix buffer, path_directory_windows buffer, path_type char(10)
    -> AttributeManager

Bookmark: 2.1 | Manipulação dos Atributos
AttributeManager
    ATTR_TABLE:
      REMOVE path_rootname (buffer)
      REMOVE path_unix (buffer)
      REMOVE path_extension (buffer)
      REMOVE path_directory_unix (buffer)
      REMOVE path_type (varchar(10))
    -> Sampler
    -> FeatureJoiner [LEFT] [off]

Bookmark: 2.2 | Extrai a amostragem
Note: Passa somente uma amostra de 10 registros para teste
Sampler
    MODE = ORIGINAL
    RATE = 10
    SAMPLE_TYPE_MULTIPLIER = -1
    SAMPLE_MODE = No
    SAMPLE_TYPE_LONG = First N Features
    SAMPLED -> SharePointOnlineConnector

Bookmark: 3.1 | Upload dos arquivos para o SHAREPOINT
Note: SharePointOnlineConnector [safe.microsoft-sharepoint.SharePointOnlineConnector Version 1] / Authentication: / Account: SolutialTech-APP / Request: / Action: Upload / Data Source: / Upload: File / File to Upload: @Value(path_windows) / Upload Options: / Site: https://solutialfme.sharepoint.com/sites/SolutialTech/ / Document Library: Documentos / Path: RR/ / If File Exists: Overwrite / Output Attributes: / Attributes to Add: _name _full_path _id _url / State: DISABLED
SharePointOnlineConnector [off]
    OPERATION_TYPE = Upload
    PARAMETER_SETUP = _FME_SOURCE_TYPE]File]_FME_SOURCE_FILE]@Value(path_windows)]_FME_SOURCE_FOLDER]<Unused>]_FME_INCLUDE_SUBFOLDERS]<Unused>]_FME_CONTENTS_ONLY]<Unused>]_FME_DATA_TO_UPLOAD]<Unused>]__microsoftsharepoint_site][{"display":"https://solutialfme.sharepoint.com/sites/SolutialTech/","value":"solutialfme.sharepoint.com,ffd72a00-7046-46c4-b36f-8ff3c5176c2f,e547c487-c2e7-49d6-b4a0-f3be40cee4fa"}]]__microsoftsharepoint_document_library][{"display":"Documentos","value":"b!ACrX_0ZwxEazb4_zxRdsL4fER-XnwtZJtKDzvkDO5PrCfDX8f5ZrQrS3vdlEPbRv"}]]_FME_UPLOAD_DESTINATION_PATH][{"display":"RR/","value":"/RR"}]]_FME_UPLOAD_ATTR_FILENAME]<Unused>]_FME_HANDLE_EXISTING_FILE]Overwrite]__microsoftsharepoint_link]NO]__microsoftsharepoint_link_permission]<Unused>]__microsoftsharepoint_link_scope]<Unused>]__microsoftsharepoint_link_expiration_date]<Unused>]_FME_ATTRIBUTES_TO_ADD]"_name _full_path _id _url"]FME_CONTROLLER_QUERY_FILE]sharepointconnector_deps/Upload.fme]FME_CONTROLLER_CHOICE]Upload
    __microsoftsharepoint_connection = SolutialTech-APP

Bookmark: 1.1 | Start do Fluxo
Note: Somente utilizado como gatilho
Creator [off]
    GEOMTYPE = Geometry Object
    NUM = 1
    CREATED -> SharePointOnlineConnector_2 [off]

Bookmark: 2.1 | Listagem dos arquivos para o SHAREPOINT
Note: SharePointOnlineConnector_2 [safe.microsoft-sharepoint.SharePointOnlineConnector Version 1] / Authentication: / Account: SolutialTech-APP / Request: / Action: List / List Options: / Site: https://solutialfme.sharepoint.com/sites/SolutialTech/ / Document Library: Documentos / Path: RR/ / Include Subfolders: Yes / Output Attributes: / Attributes to Add: _name _full_path _id _url / State: DISABLED
SharePointOnlineConnector_2 [off]
    OPERATION_TYPE = List
    PARAMETER_SETUP = __microsoftsharepoint_site][{"display":"https://solutialfme.sharepoint.com/sites/SolutialTech/","value":"solutialfme.sharepoint.com,ffd72a00-7046-46c4-b36f-8ff3c5176c2f,e547c487-c2e7-49d6-b4a0-f3be40cee4fa"}]]__microsoftsharepoint_document_library][{"display":"Documentos","value":"b!ACrX_0ZwxEazb4_zxRdsL4fER-XnwtZJtKDzvkDO5PrCfDX8f5ZrQrS3vdlEPbRv"}]]_FME_FILES][{"display":"RR/","value":"/RR"}]]_FME_INCLUDE_SUBFOLDERS]Yes]_FME_ATTRIBUTES_TO_ADD]"_name _full_path _id _url"]FME_CONTROLLER_QUERY_FILE]sharepointconnector_deps/List.fme]FME_CONTROLLER_CHOICE]List
    __microsoftsharepoint_connection = SolutialTech-APP
    -> FeatureJoiner [RIGHT] [off]

Bookmark: 3.1 | Join para fazer o DIFF
FeatureJoiner [off]
    ATTR_CONFLICT_RES_LOOKUP = USE_LEFT
    GEOMETRY_HANDLING_LOOKUP = USE_LEFT
    JOIN_KEYS = path_filename _name AUTO
    JOIN_MODE = Inner
    ATTR_CONFLICT_RES = Prefer Left
    GEOMETRY_HANDLING = Prefer Left
    UNJOINED_LEFT -> SharePointOnlineConnector_3 [off]

Bookmark: 2.2 | Upload dos arquivos para o SHAREPOINT
Note: SharePointOnlineConnector_3 [safe.microsoft-sharepoint.SharePointOnlineConnector Version 1] / Authentication: / Account: SolutialTech-APP / Request: / Action: Upload / Data Source: / Upload: File / File to Upload: @Value(path_windows) / Upload Options: / Site: https://solutialfme.sharepoint.com/sites/SolutialTech/ / Document Library: Documentos / Path: RR/ / If File Exists: Overwrite / Output Attributes: / Attributes to Add: _name _full_path _id _url / State: DISABLED
SharePointOnlineConnector_3 [off]
    OPERATION_TYPE = Upload
    PARAMETER_SETUP = _FME_SOURCE_TYPE]File]_FME_SOURCE_FILE]@Value(path_windows)]_FME_SOURCE_FOLDER]<Unused>]_FME_INCLUDE_SUBFOLDERS]<Unused>]_FME_CONTENTS_ONLY]<Unused>]_FME_DATA_TO_UPLOAD]<Unused>]__microsoftsharepoint_site][{"display":"https://solutialfme.sharepoint.com/sites/SolutialTech/","value":"solutialfme.sharepoint.com,ffd72a00-7046-46c4-b36f-8ff3c5176c2f,e547c487-c2e7-49d6-b4a0-f3be40cee4fa"}]]__microsoftsharepoint_document_library][{"display":"Documentos","value":"b!ACrX_0ZwxEazb4_zxRdsL4fER-XnwtZJtKDzvkDO5PrCfDX8f5ZrQrS3vdlEPbRv"}]]_FME_UPLOAD_DESTINATION_PATH][{"display":"RR/","value":"/RR"}]]_FME_UPLOAD_ATTR_FILENAME]<Unused>]_FME_HANDLE_EXISTING_FILE]Overwrite]__microsoftsharepoint_link]NO]__microsoftsharepoint_link_permission]<Unused>]__microsoftsharepoint_link_scope]<Unused>]__microsoftsharepoint_link_expiration_date]<Unused>]_FME_ATTRIBUTES_TO_ADD]"_name _full_path _id _url"]FME_CONTROLLER_QUERY_FILE]sharepointconnector_deps/Upload.fme]FME_CONTROLLER_CHOICE]Upload
    __microsoftsharepoint_connection = SolutialTech-APP

Bookmark: 1.1 | Start do Fluxo
Note: Somente utilizado como gatilho
Creator_2 [off]
    GEOMTYPE = Geometry Object
    NUM = 1
    CREATED -> SharePointOnlineConnector_4 [off]

Bookmark: 2.1 | Listagem dos arquivos para o SHAREPOINT
Note: SharePointOnlineConnector_4 [safe.microsoft-sharepoint.SharePointOnlineConnector Version 1] / Authentication: / Account: SolutialTech-APP / Request: / Action: List / List Options: / Site: https://solutialfme.sharepoint.com/sites/SolutialTech/ / Document Library: Documentos / Path: RR/ / Include Subfolders: Yes / Output Attributes: / Attributes to Add: _name _full_path _id _url / State: DISABLED
SharePointOnlineConnector_4 [off]
    OPERATION_TYPE = List
    PARAMETER_SETUP = __microsoftsharepoint_site][{"display":"https://solutialfme.sharepoint.com/sites/SolutialTech/","value":"solutialfme.sharepoint.com,ffd72a00-7046-46c4-b36f-8ff3c5176c2f,e547c487-c2e7-49d6-b4a0-f3be40cee4fa"}]]__microsoftsharepoint_document_library][{"display":"Documentos","value":"b!ACrX_0ZwxEazb4_zxRdsL4fER-XnwtZJtKDzvkDO5PrCfDX8f5ZrQrS3vdlEPbRv"}]]_FME_FILES][{"display":"RR/","value":"/RR"}]]_FME_INCLUDE_SUBFOLDERS]Yes]_FME_ATTRIBUTES_TO_ADD]"_name _full_path _id _url"]FME_CONTROLLER_QUERY_FILE]sharepointconnector_deps/List.fme]FME_CONTROLLER_CHOICE]List
    __microsoftsharepoint_connection = SolutialTech-APP
    -> Tester [off]

Bookmark: 3.1 | Condicional de Exemplo
Note: Tester [Tester Version 4] / Test Clauses: Left ValueOperatorRight Value@Value(_name)Begins Withca Comparison Mode: Case Insensitive / Advanced: / Preserve Feature Order: Per Output Port / State: DISABLED
Tester [off]
    BOOL_OP = OR
    TEST_CLAUSE = CASE_INSENSITIVE_TEST @Value(_name) BEGINS_WITH ca
    TEST_MODE = TEST
    PASSED -> SharePointOnlineConnector_5 [off]

Bookmark: 2.2 | Upload dos arquivos para o SHAREPOINT
Note: SharePointOnlineConnector_5 [safe.microsoft-sharepoint.SharePointOnlineConnector Version 1] / Authentication: / Account: SolutialTech-APP / Request: / Action: Delete / Delete Options: / Site: https://solutialfme.sharepoint.com/sites/SolutialTech/ / Document Library: Documentos / Path: @Value(_full_path) / State: DISABLED
SharePointOnlineConnector_5 [off]
    OPERATION_TYPE = Delete
    PARAMETER_SETUP = __microsoftsharepoint_site][{"display":"https://solutialfme.sharepoint.com/sites/SolutialTech/","value":"solutialfme.sharepoint.com,ffd72a00-7046-46c4-b36f-8ff3c5176c2f,e547c487-c2e7-49d6-b4a0-f3be40cee4fa"}]]__microsoftsharepoint_document_library][{"display":"Documentos","value":"b!ACrX_0ZwxEazb4_zxRdsL4fER-XnwtZJtKDzvkDO5PrCfDX8f5ZrQrS3vdlEPbRv"}]]_FME_FILEID]@Value(_full_path)]FME_CONTROLLER_QUERY_FILE]sharepointconnector_deps/Delete.fme]FME_CONTROLLER_CHOICE]Delete
    __microsoftsharepoint_connection = SolutialTech-APP

Bookmark: 1.1 | Start do Fluxo
Note: Somente utilizado como gatilho
Creator_3 [off]
    GEOMTYPE = Geometry Object
    NUM = 1
    CREATED -> SharePointOnlineConnector_6 [off]

Bookmark: 2.1 | Download dos arquivos para o SHAREPOINT
Note: SharePointOnlineConnector_6 [safe.microsoft-sharepoint.SharePointOnlineConnector Version 1] / Authentication: / Account: SolutialTech-APP / Request: / Action: Download / Download Options: / Site: https://solutialfme.sharepoint.com/sites/SolutialTech/ / Document Library: Documentos / Path: RR/ / Destination: / Download as: Folder / Download to Folder: D:\gitHub\SolutialTech\2024\12\sharepoint-fme\1-dataset\Nova pasta / If File Exists: Overwrite / Include Subfolders: No / State: DISABLED
SharePointOnlineConnector_6 [off]
    OPERATION_TYPE = Download
    PARAMETER_SETUP = __microsoftsharepoint_site][{"display":"https://solutialfme.sharepoint.com/sites/SolutialTech/","value":"solutialfme.sharepoint.com,ffd72a00-7046-46c4-b36f-8ff3c5176c2f,e547c487-c2e7-49d6-b4a0-f3be40cee4fa"}]]__microsoftsharepoint_document_library][{"display":"Documentos","value":"b!ACrX_0ZwxEazb4_zxRdsL4fER-XnwtZJtKDzvkDO5PrCfDX8f5ZrQrS3vdlEPbRv"}]]_FME_FILES][{"display":"RR/","value":"/RR"}]]_FME_DATA_TARGET]Folder]_FME_TARGET_ATTRIBUTE]<Unused>]_FME_ENCODING_TYPE]<Unused>]_FME_TARGET_FOLDER]D:\gitHub\SolutialTech\2024\12\sharepoint-fme\1-dataset\Nova pasta]_FME_HANDLE_EXISTING_FILE]Overwrite]_FME_INCLUDE_SUBFOLDERS]No]FME_CONTROLLER_QUERY_FILE]sharepointconnector_deps/Download.fme]FME_CONTROLLER_CHOICE]Download
    __microsoftsharepoint_connection = SolutialTech-APP

Bookmark: [UPLOAD] de Arquivos para o SHAREPOINT
Note: AttributeManager [AttributeManager Version 5] / Attribute Actions: Input AttributeOutput AttributeValueTypeActionpath_rootnamepath_rootnamebufferRemovepath_unixpath_unixbufferRemovepath_extensionpath_extensionbufferRemovepath_directory_unixpath_directory_unixbufferRemovepath_typepath_typevarchar(10)Remove
