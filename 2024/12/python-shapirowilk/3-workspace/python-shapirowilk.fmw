FME workspace python-shapirowilk.fmw

Parameters:
- qtd_registros = 5000   # Quantidade Registros (Amostragem)

Note: Inspecionar a Saída
ShapiroWilk_Saida: Inspector

Bookmark: 1.0 | Trigger
Note: Somente para dar o Gatilhor de Start do fluxo
Creator
    GEOMTYPE = Geometry Object
    NUM = 1
    CREATED -> Cloner

Bookmark: 2.1 | Criação da Amostragem
Note: Gera a quantidade de registros (CLONA) determinados nos parâmetros para a Simulação / General: / Number of Copies: 1000 / Output Attribute Name: / Copy Number: id
Cloner
    COPIES = $(qtd_registros)
    COPYATT = id
    COPY -> RandomNumberGenerator

Bookmark: 2.2 | Valores Randômicos para a Amostragem
Note: Gera os valores RANDOMICAMENTE para a amostragem dos dados / General: / Minimum Value: -1.7824 / Maximum Value: 1.1977 / Decimal Places: 8 / Output Attribute Name: / Generated Number: x
RandomNumberGenerator
    MAX = 1.1977
    MIN = -1.7824
    PLACES = 8
    RESULT_ATTR = x
    -> ShapiroWilk [Dados]

Bookmark: 3.1 | Transformer Customizado
Note: ShapiroWilk [ShapiroWilk] / [Embedded] / User Parameters: / x: @Value(x)
ShapiroWilk
    atributo_analise = @Value(x)
    Saida -> ShapiroWilk_Saida

FME custom transformer ShapiroWilk

Parameters:
- atributo_analise =   # Atributo para Análise

Bookmark: Entrada dos Dados
Note: Entrada dos Dados
Dados (input)
    -> PythonCaller

Bookmark: Aplicação do Código Python
Note: Necessita da Instalação da LIB SCIPY / Executa o código Python e retorna os atributos shapiro.result e shapiro.pvalue / A aplicação do teste ShapiroWilk consiste em analisar a normalização dos dados. Sendo o quantitativo de registros de entrada são processados, saindo somente uma linha, com o resultado da testagem.
PythonCaller
    NEW_ATTRIBUTES = shapiro.result buffer shapiro.pvalue buffer
    PYTHONSOURCE:
      import fme
      from fme import BaseTransformer
      import fmeobjects
      import scipy


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              self.x = []

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              self.x.append(feature.getAttribute('x'))

          def close(self):
              """This method is called once all the FME Features have been processed from input()."""
              results = scipy.stats.shapiro(self.x)

              feature = fmeobjects.FMEFeature()
              feature.setAttribute('shapiro.result', results[0])
              feature.setAttribute('shapiro.pvalue', results[1])

              self.pyoutput(feature)

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> AttributeKeeper

Bookmark: Mantém os Atributos para Saída
Note: AttributeKeeper [AttributeKeeper Version 3] / General: / Attributes to Keep: shapiro.pvalue,shapiro.result / Lists to Keep: <not set> / Advanced: / Feature Output: Individual Mode
AttributeKeeper
    CREATE_BULK_MODE_FEATURES = NO
    KEEP_ATTRS = shapiro.pvalue,shapiro.result
    -> Saida (output)

Bookmark: Saida dos Dados
Saida (output)
