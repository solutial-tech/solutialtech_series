FME workspace fme-chatgpt.fmw
Title: Automatizando com ChatGPT
History: 06/12/2024,Thiago Brigagão,Criação do Workspace

Parameters:
- SourceDataset_PDF2D = D:\gitHub\SolutialTech\2024\12\fme-chatgpt\1-dataset\memorial-descritivo-ZEIS.pdf   # Source Adobe Geospatial PDF File

Readers:
- PDF2D_1: PDF2D from $(SourceDataset_PDF2D)

GeometryReplacer_Output: Inspector

Bookmark: 1.1 | Leitura do PDF Memorial
Note: Referência: / http://goiana.pe.gov.br/wp-content/uploads/2020/01/memorial-descritivo-ZEIS.pdf
Note: Leitura do PDF
pdf_no_layer (reader PDF2D_1)
    -> Counter

Bookmark: 2.1 | Cria um ID Temporário
Note: Cria um contador por extração que o FME Faz. A ideia é utilizar como ID
Counter
    CNT_ATTR = id_temporario
    DOMAIN = counter
    SCOPE = Global
    START = 1
    -> NullAttributeMapper

Bookmark: 2.2 | Mapeamento de Valores Missing | Nulos | Empty | Vazios
Note: Se o valor do atributo fme_text_string for / Missing / Null / Empty / <vazio> / Assumimos que os valores acima são quebras de linhas, sendo assim, mapearemos para o valor 999.
NullAttributeMapper
    ATTRCHOICE_ACTION = SELECTED
    ATTRLIST = fme_text_string
    NEW_VALUE = 999
    NULL_TREATMENT_LU = SETVALUE
    OTHER_VALUE = " "
    SOURCE_ATTR_VAL_LU = SETNULL EMPTY MISSINGATTR
    ATTRCHOICE = Selected Attributes
    NULL_TREATMENT = New Value
    SOURCE_ATTR_VAL = Null Empty "Missing (Selected Attributes Only)"
    -> Tester

Bookmark: 2.3 | Filtragem dos Valores 999 e Alteração por <Enter>
Note: Tester [Tester Version 4] / Test Clauses: Left ValueOperatorRight Value@Value(fme_text_string)=999Advanced: / Preserve Feature Order: Per Output Port
Tester
    BOOL_OP = OR
    TEST_CLAUSE = TEST @Value(fme_text_string) = 999
    TEST_MODE = TEST
    PASSED -> StringReplacer
    FAILED -> Sorter
Note: Substituimos os valores 999 com <enter> garantindo a quebra de linha
StringReplacer
    CASE = NO
    FIND_TEXT = 999
    NO_MATCH = _FME_NO_OP_
    REGEXP = NO
    REPLACE_TEXT = "\n"
    SRC_ATTRS = fme_text_string
    -> Sorter

Bookmark: 3.1 | Ordenação dos Dados
Note: Ordena os registros com base no ID Temporário
Sorter
    SORT_PARM = id_temporario NUMERIC ASCENDING
    SORTED -> Aggregator

Bookmark: 3.2 | Agrupamento do Texto
Note: Une os textos das multiplas linhas, transformando o texto em apenas 1 linha
Aggregator
    ACCUM_ATTRS_NAME = Drop Incoming Attributes
    AGGREGATE_TYPE = Homogeneous Collection (If Possible)
    CONCAT_ATTRS = fme_text_string
    MODE = Geometry - Assemble One Level
    AGGREGATE -> StringReplacer_2

Bookmark: 3.3 | Replace do Texto
Note: Substitui " " por ""
StringReplacer_2
    CASE = NO
    FIND_TEXT = "  "
    NO_MATCH = _FME_NO_OP_
    REGEXP = NO
    REPLACE_TEXT = " "
    SRC_ATTRS = fme_text_string
    -> OpenAIChatGPTConnector

Bookmark: 1.2 | Chamada do ChatGPT
Note: RETORNO DO CHATGPT / POLYGON((277192.747 9163832.739, 277608.420 9163620.234, 277587.178 9163546.965, 277758.008 9163477.561, 277724.376 9163424.516, 277733.989 9163419.181, 277759.979 9163411.000, 277776.712 9163401.042, 277797.357 9163383.420, 277617.073 9163299.041, 277612.465 9162938.353, 277464.923 9162912.050, 277353.693 9162880.125, 277246.105 9162829.878, 277190.447 9162794.580, 277123.029 9162770.651, 277051.968 9162758.076, 277045.004 9162969.189, 277058.096 9162982.267, 277052.054 9163013.454, 277028.388 9163025.526, 277008.193 9163560.981, 277046.200 9163561.377, 277045.499 9163571.026, 277063.737 9163568.656, 277062.012 9163660.304, 277128.550 9163638.247, 277192.747 9163832.739))
Note: OpenAIChatGPTConnector / INSTRUÇÃO / Tenho um arquivo memorial descritivo e preciso extrair as coordenadas. Gostaria que você me devolvesse somente o wkt, sem nenhum texto adicional. / RESULTADO / WKT
OpenAIChatGPTConnector
    Auth =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
    BaseURL = https://api.openai.com/
    ChatHistory = NO
    Service = OpenAI
    TRANSFER_TIMEOUT_LENGTH = 360
    Version = 2023-03-15-preview
    frequency_penalty = 0
    model = gpt-4o
    n = 1
    presence_penalty = 0
    stream = false
    systemContent = Tenho um arquivo memorial descritivo e preciso extrair as coordenadas. Gostaria que você me devolvesse somente o wkt, sem nenhum texto adicional.
    temperature = 0
    top_p = 1
    userContent = @Value(fme_text_string)
    -> GeometryReplacer

Bookmark: 4.1 | Cria a Geometria
Note: Espacializa a geometria
GeometryReplacer
    KIND = wkt
    OGC_WKT_PRECISION = FLOAT_64
    REMOVE_ATTRIBUTE = Yes
    SOURCE = @Value(Response)
    KIND_LONG = OGC Well Known Text
    OGC_WKT_PRECISION_DISPLAY = 64-bit
    -> GeometryReplacer_Output
