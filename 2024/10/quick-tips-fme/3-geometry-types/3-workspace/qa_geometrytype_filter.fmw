FME workspace qa_geometrytype_filter.fmw
Title: Validação e Qualidade de Dados com FME
History: 27/10/2024,Thiago Brigagão,Criação do fluxo

Parameters:
- SourceDataset_GML = D:\gitHub\quick-tips-fme\GeometryTypes\Dataset\ContoursO8.gml   # Source Geography Markup Language (GML) File(s)

Readers:
- GML_1: GML from $(SourceDataset_GML)

Note: IMAGENS DE EXEMPLO / 1-Curva de Nível / https://github.com/solutial-tech/solutialtech_series/blob/main/2024/10/quick-tips-fme/3-geometry-types/2-imagens/1-Curva%20de%20N%C3%ADvel.png / 2-Curva de Nível-Resultado / https://github.com/solutial-tech/solutialtech_series/blob/main/2024/10/quick-tips-fme/3-geometry-types/2-imagens/2-Curva%20de%20N%C3%ADvel-Resultado.png
Note: Inspecionando: Curva de nível OK
curva_de_nivel: Inspector
Note: Log: Apresenta no Log as geometrias diferente de ÁREA e LINHA
Logger
    LOG_FEATURE = LOG_ONLY
    MAXCOORDS = 20
    MAXFEATS = 20
    MESSAGE = Feature is:
    SEVERITY = INFO

Bookmark: 1.0 | Reader GML
Contours (reader GML_1)
    attributes: Elevation xml_char(30), Grid xml_char(30), gml_pointProperty xml_geometry, gml_multiPointProperty xml_geometry, gml_curveProperty xml_geometry, gml_multiCurveProperty xml_geometry, gml_surfaceProperty xml_geometry, gml_multiSurfaceProperty xml_geometry
    -> GeometryFilter

Bookmark: 2.1 |Filtragem de Geometrias
Note: GeometryFilter [GeometryFilter Version 8] / General: / Mode: Simple / Output Ports: Line Area / Advanced: / Preserve Feature Order: Per Output Port
GeometryFilter
    FILTER_MODE = SIMPLE
    FILTER_MULTI = FILTER_TYPES]"Line Area"]FME_CONTROLLER_QUERY_FILE]]FME_CONTROLLER_CHOICE]Simple
    Curve -> curva_de_nivel
    Area -> GeometryCoercer
    <UNFILTERED> -> StatisticsCalculator

Bookmark: 2.2 | Transformando Área para Linha
Note: Transforma a AREA em LINHA
GeometryCoercer
    GQUERY:
      for $geom in //geometry
      where $geom/count(parent::geometry) = 0
      return number($geom/@fme_id)
    KIND = fme_line
    COERCED -> curva_de_nivel

Bookmark: 2.3 | Contabiliza as Geom Diferente a AREA e LINHA
Note: Counta com base no atributo ELEVATION
StatisticsCalculator
    ATTR_ACCUM_MODE = None
    CALCULATION_MODE = NUMERIC
    FEAT_STATS = Elevation,NUMERIC_MODE,,,COUNT,,,,,,,,,,
    COMPLETE -> Logger
