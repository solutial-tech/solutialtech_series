FME workspace qa_spikes_outliers_complete.fmw
Title: Validação e Qualidade de Dados com FME
Description: Exemplo de remoção de Spikes & Outliers de dados geográficos com FME
History: 22/10/2024,Thiago Brigagão,Criação de Workspace Template

Parameters:
- SourceDataset_IGDS = D:\gitHub\quick-tips-fme\2-spikes\1-dataset\bathymetry.dgn   # Source Bentley MicroStation Design File(s)

Readers:
- IGDS_1: IGDS from $(SourceDataset_IGDS) in UTM83-10

Note: IMAGENS DE EXEMPLO / 1-Spike Exemplo / https://github.com/solutial-tech/solutialtech_series/blob/main/2024/10/quick-tips-fme/2-spikes/2-images/1-Spike%20Exemplo.png / 2-SpikeRemover / https://github.com/solutial-tech/solutialtech_series/blob/main/2024/10/quick-tips-fme/2-spikes/2-images/2-SpikeRemover.png / 3-Spike Resultado / https://github.com/solutial-tech/solutialtech_series/blob/main/2024/10/quick-tips-fme/2-spikes/2-images/3-Spike%20Resultado.png / 4-Spike 45 Graus / https://github.com/solutial-tech/solutialtech_series/blob/main/2024/10/quick-tips-fme/2-spikes/2-images/4-Spike%2045%20Graus.png / 5-Spike Z / https://github.com/solutial-tech/solutialtech_series/blob/main/2024/10/quick-tips-fme/2-spikes/2-images/5-Spike%20Z.png
Note: Inspecionando Dados corrigidos de Batimetria
count_removidos_2: Inspector [off]
Note: Inspecionando: os spikes removidos
count_removidos: Inspector [off]

Bookmark: 1.0 | Reader DGN
Note: Leitor | DGN | Dados de Batimetria
1 (reader IGDS_1)
    -> SpikeRemover

Bookmark: 2.1 | Removendo Spikes
Note: SpikeRemover [SpikeRemover Version 3] / General: / Maximum Spike Angle: 10 / Maximum Spike Length: 250 / Dimension: 2D / Remove Spikes Iteratively: No
SpikeRemover
    DIMENSIONS = 2D
    ITERATIVE = No
    SPIKEANGLE = 10
    SPIKELENGTH = 250
    UNCHANGED -> Junction
    CHANGED -> Junction
    REMOVED -> StatisticsCalculator

Bookmark: 2.0 | Remoção de Spikes
Junction
    -> count_removidos_2

Bookmark: 2.2 | Count de Removidos
Note: Contagem de quantos registros removemos
StatisticsCalculator
    ATTR_ACCUM_MODE = None
    CALCULATION_MODE = NUMERIC
    FEAT_STATS = _spike_angle,NUMERIC_MODE,,,COUNT,,,,,,,,,,
    COMPLETE -> count_removidos
