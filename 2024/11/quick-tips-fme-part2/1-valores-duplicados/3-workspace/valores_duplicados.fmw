FME workspace valores_duplicados.fmw
Title: Validação e Qualidade de Dados com FME
History: 06/11/2024,Thiago Brigagão,Criação do fluxo

Parameters:
- SourceDataset_XLSXR = D:\gitHub\SolutialTech\2024\11\quick-tips-fme-part2\1-valores-duplicados\1-dataset\businesslicenses.xlsx   # Source Microsoft Excel File(s)
- DestDataset_XLSXW = $(FME_MF_DIR)output.xlsx   # Destination Microsoft Excel File

Readers:
- XLSXR_1: XLSXR from $(SourceDataset_XLSXR)

Writers:
- XLSXW_1: XLSXW to $(DestDataset_XLSXW)

Bookmark: 1.0 | Reader XLSx
Note: RecordID é um número de ID exclusivo em todo o conjunto de dados; ou seja, cada registro deve ter um valor diferente. / LicenseNumber é um número de ID que pode ser reutilizado e, portanto, pode não ser exclusivo. Além disso, podem existir vários registros para o mesmo LicenseNumber; por exemplo, uma empresa que opera em vários endereços terá um registro no conjunto de dados para cada endereço (mas com o mesmo LicenseNumber). / LicenseRSN é um número de ID exclusivo por licença; ou seja, cada licença emitida deve ter um LicenseRSN exclusivo. Claro, pode haver múltiplos registros com este valor, pois ele deve corresponder a cada registro de uma característica de múltiplos LicenseNumber.
Business_Licences (reader XLSXR_1)
    attributes: RecordID number(4,0), LicenceRSN number(7,0), LicenceNumber char(9), BusinessTradeName char(40), Status char(20), IssuedDate char(19), ExpiredDate char(19), BusinessType char(13), Number char(7), Street char(31), City char(18), Province char(2), Country char(3), PostalCode char(10), LocalArea char(28), NumberOfEmployees number(4,0), FeePaid number(7,2)
    -> DuplicateFilter

Bookmark: 2.1 | Verificação RecordID Duplicado
Note: Filtragem com de dados com base no atributo RecordID
DuplicateFilter
    INPUT_ORDERED_CHOICE = No
    KEYATTR = RecordID
    UNIQUE -> Matcher
    DUPLICATE -> AttributeCreator

Bookmark: 2.2 | Verificação de LicenceRSN para LicenceNumber
Note: Essa configuração faz com que caso o LicenceRSN esteja para mais de um LicenceNumber seja apresentado na Porta Matched.
Note: Desabilite a opção > "Check Geometry" / Attribute Matching Strategy: Match Selected Attributes / Selected Attributes: LicenceRSN / Attributes That Must Differ: LicenceNumber
Matcher
    BLANK_AND_MISSING_DIFFER = No
    CHECK_TYPES_AND_ENCODINGS = No
    CNT_ATTR = _match_id
    DIFFATTRS = LicenceNumber
    MATCHATTRS = LicenceRSN
    MATCH_STRATEGY = Match Selected Attributes
    SINGLE_MATCHED -> AttributeCreator_2
    NOT_MATCHED -> Tester

Bookmark: 2.3 | Filtra somente as Licences em Uso
Note: É necessário para minimizar erros verificar somente as licenças Válidas com o status de Issued
Tester
    BOOL_OP = OR
    TEST_CLAUSE = TEST @Value(Status) = Issued
    TEST_MODE = TEST
    PASSED -> Matcher_2

Bookmark: 2.4 | Verificação de LicenceNumber p/ LicenceRSN
Note: Essa configuração faz com que caso o LicenceNumber esteja para mais de um LicenceRSN seja apresentado na Porta Matched.
Note: Desabilite a opção > "Check Geometry" / Attribute Matching Strategy: Match Selected Attributes / Selected Attributes: LicenceNumber / Attributes That Must Differ: LicenceRSN
Matcher_2
    BLANK_AND_MISSING_DIFFER = No
    CHECK_TYPES_AND_ENCODINGS = No
    CNT_ATTR = _match_id
    DIFFATTRS = LicenceRSN
    MATCHATTRS = LicenceNumber
    MATCH_STRATEGY = Match Selected Attributes
    SINGLE_MATCHED -> AttributeCreator_3
    NOT_MATCHED -> Sheet1 (writer XLSXW_1)

Bookmark: 4.1 | Writer XLSx
Note: Licenças em Uso
Sheet1 (writer XLSXW_1)
    attributes: RecordID number(4), LicenceRSN number(7), LicenceNumber string(9), BusinessTradeName string(40), Status string(20), IssuedDate string(19), ExpiredDate string(19), BusinessType string(13), Number string(7), Street string(31), City string(18), Province string(2), Country string(3), PostalCode string(10), LocalArea string(28), NumberOfEmployees number(4), FeePaid number(7)

Bookmark: 3.2 | LicenceRSN para MAIS de um LicenceNumber
Note: Foi encontrado valores mais de um registro para o LicenceNumber. / Verificar o registro: / RecordID:@Value(RecordID) / LicenceNumber:@Value(LicenceNumber) / LicenceRSN: @Value(LicenceRSN)
AttributeCreator_3
    ATTR_TABLE:
      SET_TO mensagem_erro (varchar(200)) = Foi encontrado valores mais de um registro para o LicenceNumber.
        Verificar o registro:
        RecordID:@Value(RecordID)
        LicenceNumber:@Value(LicenceNumber)
        LicenceRSN: @Value(LicenceRSN)
    -> Junction

Bookmark: 3.2 | LicenceRSN para MAIS de um LicenceNumber
Note: Foi encontrado valores mais de um registro para o LicenceRSN. / Verificar o registro: / LicenceRSN: @Value(LicenceRSN) / LicenceNumber:@Value(LicenceNumber) / RecordID:@Value(RecordID)
AttributeCreator_2
    ATTR_TABLE:
      SET_TO mensagem_erro (varchar(200)) = Foi encontrado valores mais de um registro para o LicenceRSN.
        Verificar o registro:
        RecordID:@Value(RecordID)
        LicenceRSN: @Value(LicenceRSN)
        LicenceNumber:@Value(LicenceNumber)
    -> Junction

Bookmark: 3.1 | RecordID Duplicado
Note: O registro RecordID: @Value(RecordID) está duplicado na base de dados.
AttributeCreator
    ATTR_TABLE = SET_TO mensagem_erro (varchar(200)) = O registro RecordID: @Value(RecordID) está duplicado na base de dados.
    -> Junction

Bookmark: 4.2 | Writer XLSx
Junction
    -> analisar_dados (writer XLSXW_1)
Note: Aba do XLS que contém os pontos a serem verificados
analisar_dados (writer XLSXW_1)
    attributes: mensagem_erro string(50), RecordID number(4), LicenceRSN number(7), LicenceNumber string(9), BusinessTradeName string(40), Status string(20), IssuedDate string(19), ExpiredDate string(19), BusinessType string(13), Number string(7), Street string(31), City string(18), Province string(2), Country string(3), PostalCode string(10), LocalArea string(28), NumberOfEmployees number(4), FeePaid number(7)
