FME workspace vertices_duplicados.fmw

Parameters:
- PARAMETER =   # SourceDataset_DGNV8 Parâmetros | Entrada
- SourceDataset_DGNV8 = D:\gitHub\SolutialTech\2024\11\quick-tips-fme-part2\2-vertices-duplicados\1-dataset\buildings.dgn   # DGN
- PARAMETER_2 =   # DestDataset_SHAPEFILE_3 Parâmetros | Saída
- DestDataset_SHAPEFILE_3 = D:\gitHub\SolutialTech\2024\11\quick-tips-fme-part2\2-vertices-duplicados\3-workspace   # Shapefile

Readers:
- DGNV8_1: DGNV8 from $(SourceDataset_DGNV8)

Writers:
- SHAPEFILE_1: SHAPEFILE to $(DestDataset_SHAPEFILE_3)

Bookmark: 1.0 | Reader DGN
Note: General Parameters: / Reader Type: Bentley MicroStation Design (V8) / Level Name: BuildingFootprints / Reader: buildings [DGNV8] / Allowed Geometries: All
BuildingFootprints (reader DGNV8_1)
    -> GeometryValidator

Bookmark: 2.1 | Validação e Correção da Geometria
Note: GeometryValidator [GeometryValidator Version 8] / Validation: / Set of Issues to Detect: Custom Issue To DetectParametersDuplicate Consecutive PointsZ Values: Include Z Values / Tolerance: 0.0Output: / Detected Issue List Name: _issues / Attempt Repair: Yes / Summary mode: Detailed
GeometryValidator
    ISSUE_ATTR_NAME = _issues
    PRESETS = Custom
    REPAIR = Yes
    RULES = CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D
    SUMMARY = Detailed
    PASSED -> BuildingFootprints (writer SHAPEFILE_1)
    REPAIRED -> BuildingFootprints (writer SHAPEFILE_1)
    ISSUE_LOCATIONS -> AttributeManager

Bookmark: 3.1 | Writer SHAPEFILE - OK
Note: Gravação do Shapefile com as LINHAS contendo os Dados Válidos + Corrigidos
BuildingFootprints (writer SHAPEFILE_1)

Bookmark: 3.1 | Pontos Duplicados
Note: O erro @Value(issue_found) foi identificado pela validação. Verificar o shape de erros.
AttributeManager
    ATTR_TABLE:
      SET_TO msg_erro (varchar(200)) = O erro @Value(issue_found) foi identificado pela validação. Verificar o shape de erros.
      RENAME_SET_VALUE issue_found > erro_ident (buffer)
      REMOVE count (uint32)
      REMOVE details (uint32)
    -> BuildingFootprints_Falhas (writer SHAPEFILE_1)

Bookmark: 3.2 | Writer SHAPEFILE - Falhas
Note: Shapefile com as Falhas
BuildingFootprints_Falhas (writer SHAPEFILE_1)
    attributes: msg_erro varchar(60), erro_ident varchar(60)
