FME workspace send_email_fmeform.fmw
Title: Envios Eficientes: Domine a Automação de E-mails com a solução de ETL FME!
History: 23/11/2024,Thiago Brigagão,Criação do fluxo

Parameters:
- PARAMETER =   # Parâmetros de Entrada
- SourceDataset_WFS = http://wfs.geosampa.prefeitura.sp.gov.br/geoserver/geoportal/wfs   # WFS | Subprefeituras
- SourceDataset_WFS_5 = http://wfs.geosampa.prefeitura.sp.gov.br/geoserver/geoportal/wfs   # WFS | Ocorrências
- SourceDataset_XLSXR = D:\gitHub\SolutialTech\2024\11\send-email-fme\1-dataset\email_responsaveis.xlsx   # Responsáveis por Subprefeitura

Readers:
- WFS_1: WFS from $(SourceDataset_WFS)
- WFS_2: WFS from $(SourceDataset_WFS_5)
- XLSXR_1: XLSXR from $(SourceDataset_XLSXR)

Note: ATENÇÃO / Você deve configurar o Transformer EMAILER para que esse fluxo funcione corretamente; / Os e-mails no XLS de responsáveis são e-mails ficticios. Altere por e-mails válidos caso você teste este template.

Bookmark: 1.1 | WFS Geosampa - Subprefeituras
Note: General Parameters: / Reader Type: OGC WFS (Web Feature Service) / Feature Type Name: subprefeitura / Reader: wfs [WFS] - 2 / Allowed Geometries: All / Exposed Attributes: NameTypecd_identificador_subprefeituraxml_real64cd_subprefeituraxml_buffernm_subprefeituraxml_buffer
subprefeitura (reader WFS_2)
    attributes: gml_parent_id xml_buffer, gml_parent_property xml_buffer, gml_id xml_buffer, cd_identificador_subprefeitura xml_real64, ge_poligono xml_geometry, cd_subprefeitura xml_buffer, nm_subprefeitura xml_buffer, tx_escala xml_buffer, tx_escala.xsi_nil xml_boolean, sg_fonte_original xml_buffer, dt_criacao xml_date, cd_tipo_discrepancia xml_int32, dt_atualizacao xml_datetime, cd_usuario_atualizacao xml_buffer, cd_usuario_atualizacao.xsi_nil xml_boolean, sg_subprefeitura xml_buffer, sg_subprefeitura.xsi_nil xml_boolean, qt_area_quilometro xml_real64, qt_area_quilometro.xsi_nil xml_boolean, qt_area_metro xml_real64, qt_area_metro.xsi_nil xml_boolean
    -> SpatialFilter [Filter]

Bookmark: 1.2 | WFS Geosampa - Queda de Árvore
Note: General Parameters: / Reader Type: OGC WFS (Web Feature Service) / Feature Type Name: risco_ocorrencia_queda_arvore / Reader: wfs [WFS] - 1 / Allowed Geometries: All / Exposed Attributes: NameTypedt_ocorrenciaxml_datedc_tipo_ocorrenciaxml_buffer
risco_ocorrencia_queda_arvore (reader WFS_1)
    attributes: gml_parent_id xml_buffer, gml_parent_property xml_buffer, gml_id xml_buffer, cd_identificador xml_buffer, cd_identificador.xsi_nil xml_boolean, dt_ocorrencia xml_date, dt_ocorrencia.xsi_nil xml_boolean, dc_tipo_ocorrencia xml_buffer, dc_tipo_ocorrencia.xsi_nil xml_boolean, nm_distrito xml_buffer, nm_distrito.xsi_nil xml_boolean, ge_ponto xml_geometry, dt_carga xml_date, dt_carga.xsi_nil xml_boolean, nm_subprefeitura xml_buffer, nm_subprefeitura.xsi_nil xml_boolean, sg_fonte_original xml_buffer, sg_fonte_original.xsi_nil xml_boolean
    -> SpatialFilter [Candidate]

Bookmark: 2.1 - Relacionamento para Recuperar as Ocorrências x Subprefeituras
Note: Relacionamento espacial entre as camadas. / Merger Filter / Conflit Resolution: Use Filter
SpatialFilter
    AGGREGATE_HANDLING = Yes
    ATTR_ACCUM_MODE = Merge Filter
    ATTR_CONFLICT_RES = Use Filter
    BASE_TYPE = Multiple Filters
    CURVE_BOUNDARY_RULE_PARAM = Default Rule
    PASS_CRITERIA = Pass Against One Filter
    PREDATTR = _predicate
    PREDICATES = INTERSECTS
    USE_BOUNDING_BOX = No
    PASSED -> Reprojector

Bookmark: 2.2 - Passa de Sirgas2000 para WGS84
Note: Reprojeta de SIRGAS2000.UTM-23S para WGS84
Reprojector
    DEST = LL-WGS84
    INTERPOLATION_TYPE_NAME = Nearest Neighbor
    RASTER_CELL_SIZE = Preserve Cells
    RASTER_TOLERANCE = 0.0
    REPROJECTED -> CoordinateExtractor

Bookmark: 2.3 - Extrai as Coordenadas dos Pts
Note: Extrai o X e Y dos pontos de QUEDA DE ÁRVORES
CoordinateExtractor
    IND = 0
    MODE = Specify Coordinate
    X_ATTR = _x
    Y_ATTR = _y
    -> FeatureJoiner [LEFT]

Bookmark: 3.0 | XLS - Leitura dos E-mails dos Responsáveis
Note: XLS com: / O NOME do responsável / E-MAIL do responsável
Plan1 (reader XLSXR_1)
    attributes: Subprefeitura char(25), Responsavel char(8), Email char(27)
    -> FeatureJoiner [RIGHT]

Bookmark: 3.1 | Relacionamento e JOIN
Note: Join para recuperar para relacionar pelo nome da SUBPREFEITURA, com o objetivo de recuperar o NOME do responsável e E-MAIL
FeatureJoiner
    ATTR_CONFLICT_RES = Prefer Left
    GEOMETRY_HANDLING = Prefer Left
    JOIN_KEYS = nm_subprefeitura Subprefeitura AUTO
    JOIN_MODE = Inner
    JOINED -> AttributeManager

Bookmark: 3.2 | Manipulação de Atributos e Ordenação dos Dados
Note: De/PARA - Renomeando os atributos
AttributeManager
    ATTR_TABLE:
      RENAME_SET_VALUE Subprefeitura > subprefeitura (varchar(25))
      RENAME_SET_VALUE Email > email (varchar(27))
      RENAME_SET_VALUE Responsavel > responsavel (varchar(8))
      RENAME_SET_VALUE dc_tipo_ocorrencia > tipo_ocorrencia (buffer)
      RENAME_SET_VALUE _x > logintude (real64)
      RENAME_SET_VALUE _y > latitude (real64)
      REMOVE _predicate (buffer)
      REMOVE nm_subprefeitura (buffer)
      REMOVE cd_identificador_subprefeitura (real64)
      REMOVE cd_subprefeitura (buffer)
    -> Sorter
Note: Sorter [Sorter Version 3] / Sort By: AttributeAlpha/NumOrderresponsavelNaturalAscendingdt_ocorrenciaNaturalAscending
Sorter
    SORT_PARM = responsavel NATURAL ASCENDING dt_ocorrencia NATURAL ASCENDING
    SORTED -> FeatureWriter [Output]

Bookmark: 3.3 | XLS - Gravação dos Registros por RESPONSÁVEL
Note: FeatureWriter [FeatureWriter Version 0] / Writer: / Format: XLSXW / Dataset: D:\gitHub\SolutialTech\2024\11\send-email-fme\3-workspace\output\@Value(responsavel).xlsx / Coordinate System: Same as source / Summary Port - Output Attribute Names: / Dataset: _dataset / Total Features Written: _total_features_written / Feature Types List Name: _feature_types / Additional Summary Port Attributes: <not set> / Output Ports: / [x] One per Feature Type
FeatureWriter
    DATASET = $(FME_MF_DIR_ENCODED)output\@Value(responsavel).xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = YES
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
    -> Sampler

Bookmark: 4.1 | Extração de Amostragem
Note: Tira uma AMOSTRAGEM de 10 últimos registros por RESPONSÁVEL
Sampler
    GROUP_BY = responsavel
    RATE = 10
    SAMPLE_MODE = No
    SAMPLE_TYPE_LONG = Last N Features
    SAMPLED -> DateTimeConverter

Bookmark: 4.2 | Geração da Tabela HTML
Note: Converte a data / %Y-%m-%d para / %d/%m/%Y
DateTimeConverter
    DATETIME_ATTR = dt_ocorrencia
    IN_FORMAT = %Y-%m-%d
    OUT_FORMAT = %d/%m/%Y
    PASSTHROUGH = NO
    REPAIR_INPUT = YES
    -> AttributeRounder
Note: Mantém somente 2 casas decimais
AttributeRounder
    PLACES = 2
    ROUND_TYPE = Nearest
    SRC_ATTRS = latitude logintude
    -> HTMLReportGenerator
Note: Cria a Tabela HTML agrupada por RESPONSÁVEL
HTMLReportGenerator
    CONTENT_LIST = TABLE
    GROUP_BY = responsavel email
    PAGE_CONFIG = TABLE{{STYLE;DEFAULT;TABLE;tipo_ocorrencia|Tipo Ocorrência/subprefeitura|Subprefeitura/dt_ocorrencia|Data Ocorrência/logintude|Logintude/latitude|Latitude;FME_CONTROLLER_QUERY_FILE;transformers/dependencies/html5/Table.fme;FME_CONTROLLER_CHOICE;Table}}
    -> AttributeManager_2

Bookmark: 4.3 | Preparação do HTML
Note: Gera os atributos: / assunto: Assunto do E-mail dinâmico com o nome do responsável / email_html: Código HTML completo que será base do E-maill
AttributeManager_2
    ATTR_TABLE:
      SET_TO assunto (varchar(200)) = Responsável: @Value(responsavel) | Queda de Árvores & Acompanhamento
      SET_TO email_html (varchar(200)) = <!DOCTYPE html>
        <html lang="pt-br">
        <head>
            <meta charset="UTF-8">
            <meta name="viewport" content="width=device-width, initial-scale=1.0">
            <title>Relatório de Ocorrências - Quedas de Árvores</title>
            <style>
                /* Estilos básicos para garantir que o e-mail seja responsivo e legível */
                body {
                    font-family: Arial, sans-serif;
                    color: #333;
                    margin: 0;
                    padding: 0;
                    background-color: #f4f4f4;
                }
                table {
                    width: 100%;
                    border-collapse: collapse;
                    margin: 20px 0;
                }
                table th, table td {
                    padding: 8px;
                    border: 1px solid #ddd;
                    text-align: left;
                }
                table th {
                    background-color: #13123E;
        			color: #fff;
                }

        		tr:hover {
                    background-color: #f1f1f1;
                }

                .email-container {
                    max-width: 600px;
                    margin: 0 auto;
                    background-color: #ffffff;
                    padding: 20px;
                    border-radius: 8px;
                }
                .header {
                    text-align: center;
                }
                .header img {
                    max-width: 100%;
                    height: auto;
                }
                .content {
                    margin-top: 20px;
                }
                .footer {
                    text-align: center;
                    font-size: 12px;
                    color: #777;
                    margin-top: 30px;
                }
                .attachment {
                    margin-top: 20px;
                    padding: 10px;
                    background-color: #e8f4f8;
                    border: 1px solid #bcd8e6;
                    border-radius: 4px;
                }
                .attachment a {
                    color: #007bff;
                    text-decoration: none;
                }
            </style>
        </head>
        <body>
            <div class="email-container">
                <!-- Cabeçalho com logo -->
                <div class="header">
                    <img src="https://i.imgur.com/Ks2h5qK.png" alt="Logo da Empresa">
                </div>

                <!-- Texto de apresentação -->
                <div class="content">
                    <p>Prezado(a),</p>
                    <p>Segue o relatório com as 10 últimas ocorrências de quedas de árvores no sistema, conforme solicitado.</p>
                </div>

                <!-- Tabela com as 10 últimas ocorrências -->
                <div class="content">
                    <h3>Últimas Ocorrências de Quedas de Árvores</h3>
                    @Value(html_content)
                </div>

                <!-- Anexo do Excel -->
                <div class="attachment">
                    <p>Você pode baixar o relatório completo de ocorrências do ano no formato Excel em anexo.</p>
                </div>

                <!-- Rodapé -->
                <div class="footer">
                    <p>Atenciosamente,</p>
                      <p>Equipe de Suporte Solutial</p>
                    <p><small>Este é um e-mail automatizado. Por favor, não responda.</small></p>
                </div>
            </div>
        </body>
        </html>

      REMOVE html_content (buffer)
    USER_EXPOSED_ATTRIBUTES = Responsavel,subprefeit,html_content,Subprefeitura
    -> Tester

Bookmark: 4.4 | Envio do EMAIL com o ANEXO
Tester
    BOOL_OP = OR
    TEST_CLAUSE = TEST @Value(email) = solutialtech@hotmail.com
    TEST_MODE = TEST
    PASSED -> Emailer
Emailer
    ATTACHMENTTABLE = $(FME_MF_DIR_ENCODED)output\@Value(responsavel).xlsx  autodetect
    BODY = @Value(email_html)
    FROM = "Solutial Tech Flow" <suporte@solutial.com.br>
    SERVICE = Gmail
    SMTP_CONNECTION = GMAIL_NAMED_CONNECTION;Suporte-Email;TIMEOUT;60;EMAIL_OPERATION;SEND_EMAIL;FME_CONTROLLER_QUERY_FILE;dependencies/Gmail.fme;FME_CONTROLLER_CHOICE;Gmail
    SUBJECT = @Value(assunto)
    TO = @Value(email)

Bookmark: 4.0 | Preparação, geração do HTML e Envio de Email
Note: Remover!!!
Note: Emailer [safe.emailer.Emailer Version 1] / Service: / Email Service: Gmail / Connection: / Gmail Connection: Suporte-Email / Timeout (seconds): 60 / Request: / Action: Send to Recipients / Addressing: / From: "Solutial Tech Flow" <suporte@solutial.com.br> / To: @Value(email) / Cc: <not set> / Bcc: <not set> / Message: / Subject: @Value(assunto) / Body: @Value(email_html) / Headers: / Headers: <not set> / Attachments: Source FileContent IDMIME TypeD:\gitHub\SolutialTech\2024\11\send-email-fme\3-workspace\output\@Value(responsavel).xlsxautodetect
