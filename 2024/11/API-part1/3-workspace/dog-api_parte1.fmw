FME workspace dog-api_parte1.fmw
Title: API: Dados e Resultados | Simplificando a interface com APIs com solução ETL FME Form
History: 14/11/2024,Thiago Brigagão,Criação do fluxo

Parameters:
- PARAMETER =   # Parâmetros de Entrada
- param_api = https://api.thedogapi.com/v1/   # https API
- token =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   # Token
- PARAMETER_2 =   # DestDataset_XLSXW Parâmetros de Saída
- DestDataset_XLSXW = $(FME_MF_DIR)output.xlsx   # Excel

Writers:
- XLSXW_1: XLSXW to $(DestDataset_XLSXW)

Note: COMO GERAR O TOKEN / Acessar o DOG API e criar um TOKEN de acesso para você em https://thedogapi.com/signup / Você receberá o token por e-mail. Acessar o e-mail e incluir o token nos parâmetros do FME / DOCUMENTAÇÃO / The Dog API - Documentação
Note: ATENÇÃO / Incluir o Token para o correto funcionamento do fluxo. / PRIMEIROS PASSOS / A API atualmente funciona sem o Token, porém, o resultado retornado é diferente. Mesmo sem o token ela funcionará, mas o fluxo a seguir foi desenvolvido com a API para aumentar o número de retornos da primeira página.

Bookmark: 1.0 | Start do Fluxo
Note: Utilizado como gatilho para dar o start no fluxo
Creator
    GEOMTYPE = Geometry Object
    NUM = 1
    CREATED -> HTTPCaller_2

Bookmark: 2.1 | GET para a API - Buscando Dados
Note: API / https://api.thedogapi.com/v1 / Method / GET / Hearders / Content-Type: application/json / x-api-key: <seu TOKEN da Dog API> / QueryString / size=thumb / mime_types=jpg / format=json / has_breeds=true / order=RANDOM / page=0 / limit=25
HTTPCaller_2
    CONNECTION_TIMEOUT_LENGTH = 60
    CUSTOM_HEADERS = Content-Type;application/json x-api-key;$(token)
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.thedogapi.com/v1/images/search?size=small&mime_types=jpg&format=json&has_breeds=true&order=RANDOM&page=0&limit=25
    TRANSFER_TIMEOUT_LENGTH = 90
    USE_COOKIES = No
    VERIFY_SSL_CERTIFICATES = Yes
    -> JSONFragmenter

Bookmark: 2.2 | Fragmentando o Json para recuperar a URL
Note: { / "breeds":[ / { / "weight":{ / "imperial":"30 - 45", / "metric":"14 - 20" / }, / "height":{ / "imperial":"18 - 22", / "metric":"46 - 56" / }, / "id":50, / "name":"Border Collie", / "bred_for":"Sheep herder", / "breed_group":"Herding", / "life_span":"12 - 16 years", / "temperament":"Tenacious, Keen, Energetic, Responsive, Alert, Intelligent", / "reference_image_id":"sGQvQUpsp" / } / ], / "id":"LtMYL_t3J", / "url":"https://cdn2.thedogapi.com/images/LtMYL_t3J.jpg", / "width":1080, / "height":1080 / },
Note: Para a extração da URL precisamos verificar os atributos que estão na raiz de retorno, sendo assim usamos o json[*] para extrair os atributos em negrito
JSONFragmenter
    EXPLODE_FORMAT = JSON
    EXTRACT_ATTR = Yes
    JSON_ATTR = _response_body
    JSON_QUERY = json[*]
    NEW_ATTRIBUTES = url buffer
    READ_FROM_FILE = NO
    RECURSIVE = NO
    REJECT_EMPTY_LISTS = YES
    FRAGMENTS -> JSONFragmenter_2

Bookmark: 2.3 | Fragmentando o Json para recuperar BREEDS
Note: { / "breeds":[ / { / "weight":{ / "imperial":"30 - 45", / "metric":"14 - 20" / }, / "height":{ / "imperial":"18 - 22", / "metric":"46 - 56" / }, / "id":50, / "name":"Border Collie", / "bred_for":"Sheep herder", / "breed_group":"Herding", / "life_span":"12 - 16 years", / "temperament":"Tenacious, Keen, Energetic, Responsive, Alert, Intelligent", / "reference_image_id":"sGQvQUpsp" / } / ], / "id":"LtMYL_t3J", / "url":"https://cdn2.thedogapi.com/images/LtMYL_t3J.jpg", / "width":1080, / "height":1080 / },
Note: Para a extração da URL precisamos verificar os atributos que estão na raiz de retorno, sendo assim usamos o json["breeds"][*] para extrair dentro de breeds
JSONFragmenter_2
    EXPLODE_FORMAT = JSON
    EXTRACT_ATTR = Yes
    JSON_ATTR = _response_body
    JSON_QUERY = json["breeds"][*]
    NEW_ATTRIBUTES = id buffer name buffer country_code buffer bred_for buffer breed_group buffer life_span buffer temperament buffer reference_image_id buffer
    READ_FROM_FILE = NO
    RECURSIVE = NO
    REJECT_EMPTY_LISTS = YES
    FRAGMENTS -> AttributeManager_3

Bookmark: 2.4 | Removento Atributos não Necessários
Note: AttributeManager_3 [AttributeManager Version 5] / Attribute Actions: Input AttributeOutput AttributeValueTypeAction_response_body_response_bodybufferRemovejson_typejson_typebufferRemovejson_indexjson_indexuint32Remove_creation_instance_creation_instanceuint64Remove_http_status_code_http_status_codebufferRemove
AttributeManager_3
    ATTR_TABLE:
      REMOVE _response_body (buffer)
      REMOVE json_type (buffer)
      REMOVE json_index (uint32)
      REMOVE _creation_instance (uint64)
      REMOVE _http_status_code (buffer)
    USER_EXPOSED_ATTRIBUTES = _http_status_code
    -> ImageFetcher

Bookmark: 3.1 | Request para Busca da Image Baseando na URL
Note: Similar ao Transformer HTTPCaller o Transformer ImageFetcher faz a requisição para o endereço com o objetivo de fazer um GET na URL e trazer para a memória a imagem retornarnada.
Note: Busca e download da imagem com base na URL retornada do GET realizado.
ImageFetcher
    CONNECTION_TIMEOUT_LENGTH = 60
    ERROR_ATTR = _http_error
    FOLLOW_REDIRECTS = Yes
    MAX_TRANSFERS_IN_PROGRESS = 1
    RASTER_TYPE = <Auto-Detect from HTTP Headers>
    RESPONSE_HEADER_LIST_ATTR = _http_headers
    STATUS_CODE_ATTR = _http_status_code
    TRANSFER_TIMEOUT_LENGTH = 90
    URL = @Value(url)
    USE_COOKIES = No
    VERIFY_SSL_CERTIFICATES = Yes
    RASTER -> AttributeManager_4

Bookmark: 3.2 | Posicionando a Imagem no Raster
Note: Atributos para posicionamento do / RASTER/ Imagem no XLS / xlsx_col_id / xlsx_row_id
AttributeManager_4
    ATTR_TABLE:
      SET_TO xlsx_col_id (uint8) = 0
      SET_TO xlsx_row_id (uint8) = 5
      REMOVE _http_status_code (buffer)
      REMOVE _http_headers{}.name (buffer)
      REMOVE _http_headers{}.value (buffer)
      REMOVE fme_basename (buffer)
    USER_EXPOSED_ATTRIBUTES = _creation_instance,json_index,fme_basename,_http_headers{}.name,_http_headers{}.value
    -> Sheet1 (writer XLSXW_1)

Bookmark: 4.1 | Writer XLSx
Note: As ABAS do arquivo XLS terão como base o atributo NAME que é a raça do DOG
Sheet1 (writer XLSXW_1)
    attributes: id string(20), url string(20), name string(20), country_code string(20), bred_for string(20), breed_group string(20), life_span string(20), temperament string(20), reference_image_id string(20)
