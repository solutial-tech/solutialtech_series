FME workspace 2-datamasking.fmw

Parameters:
- SourceDataset_MSSQL_ADO = SQLServer (Localhost)   # SQL Server Connection
- DestDataset_MSSQL_ADO = SQLServer (Localhost)   # SQL Server Connection

Readers:
- MSSQL_ADO_1: MSSQL_ADO from $(SourceDataset_MSSQL_ADO)

Writers:
- MSSQL_ADO_2: MSSQL_ADO to $(DestDataset_MSSQL_ADO)

Bookmark: Possibilidade 1
Note: Responsável por gerar usuários (Nome, Sobrenome, Idade, Telefone, entre outros ) parar utilizarmos dentro de nosso workspace
RandomUserCreator_2 [off]
    gender = all
    nationaility = BR
    results = @Value(First_Name.total_count)

Bookmark: 1.0 | Tabela no SQL SERVER
Note: Leitura do SQL Server referente a / Tabela criada no Fluxo FME Apresentado na etapa 1
airline_dataset (reader MSSQL_ADO_1)
    attributes: Passenger_ID varchar(6), First_Name varchar(15), Last_Name varchar(25), Gender varchar(6), Age integer, Nationality varchar(44), Airport_Name varchar(66), Airport_Country_Code varchar(2), Country_Name varchar(44), Airport_Continent varchar(3), Continents varchar(13), Departure_Date datetime, Arrival_Airport varchar(3), Pilot_Name varchar(31), Flight_Status varchar(9)
    -> AttributeCopier

Bookmark: 2.1 | Copiando os Atributos
Note: Utilizamos apenas para copiar os atributos que iremos mascarar, com a finalidade de mostrarmos no episódio como ficarão os dados alterados
AttributeCopier
    ATTR_TABLE:
      COPY First_Name > C_First_Name
      COPY Last_Name > C_Last_Name
      COPY Pilot_Name > C_Pilot_Name
    MISSING_INPUT_ATTRS = REMOVE
    -> RandomNumberGenerator

Bookmark: 2.2 | Gerando a AGE (Idade) Randomicamente
Note: Minimum Value: 18 / Maximum Value: 82
RandomNumberGenerator
    MAX = 82
    MIN = 18
    PLACES = 0
    RESULT_ATTR = Age
    -> StringReplacer

Bookmark: 3.1 | Mascaramento: Substituição de Valores por X
Note: Utiliza o REPLACE de cada caractere por um novo caractere (X) / Essa ação é realizada com a utilização de REGEX (Expressão Regular) / "\S" Matches any non-whitespace character / Utilizamos o AI Assist de apoio para gerar a REGEX
StringReplacer
    CASE = NO
    FIND_TEXT = \S
    NO_MATCH = _FME_NO_OP_
    REGEXP = YES
    REPLACE_TEXT = X
    SRC_ATTRS = First_Name,Last_Name,Pilot_Name
    TEST_STRING:
      Hello
      world
      regex123
      a
      1
      !
    -> airline_dataset_mask (writer MSSQL_ADO_2)

Bookmark: 2.0 | Tabela Anonimizada
Note: Gravação da tabela de saída com os dados anonimizados
airline_dataset_mask (writer MSSQL_ADO_2) [off]
    attributes: Passenger_ID varchar(6), First_Name varchar(15), Last_Name varchar(25), Gender varchar(6), Age integer, Nationality varchar(44), Airport_Name varchar(66), Airport_Country_Code varchar(2), Country_Name varchar(44), Airport_Continent varchar(3), Continents varchar(13), Departure_Date datetime, Arrival_Airport varchar(3), Pilot_Name varchar(31), Flight_Status varchar(9)

Bookmark: Possibilidade 2
Note: Embaralhamento dos REGISTROS
FeatureShuffler_2 [off]
    ShuffleType = FY

Bookmark: Possibilidade 3
Note: Criptografia
AttributeCompressor [off]
    COMPRESSION_LEVEL = 0
    ENCRYPTION_TYPE_LOOKUP = AES-256
    ENCRYPTION_TYPE = AES-256

Bookmark: Possibilidade 4
Note: Descriptografia
AttributeDecompressor [off]
    ATTR_ENCODING = fme-binary
    ENCRYPTION_TYPE_LOOKUP = NONE
    ENCRYPTION_TYPE = None

Bookmark: Possibilidade 5
Note: Encode do Texto
TextEncoder_2 [off]
    DEST_ATTR = _encoded
    ENCODING_TYPE = BASE64_ENCODE
    STRING_TO_ENCODE = @Value(Pilot_Name)

FME custom transformer FeatureShufflerLoop

Parameters:
- _SHUFFLERCT_FEATURECOUNT = @Value(_ShufflerCT_FeatureCount)   # Shufflerct Featurecount
- SRC_LIST = _ShufflerCT_List{}._ShufflerCT_ID   # "" List Attribute
- LIST_ATTR = _ShufflerCT_List{}   # "" List Attribute

RandomNumberGenerator_2_Input (input)
    -> Tester
Note: The condition that ends the loop (are we down to zero features yet, remembering that elements are numbered from zero in a list)
Note: The selection/sort works by picking a feature at random and shuffling it to the bottom of the list. It repeats this until all features have been selected. / If FME allowed an element to be removed from a list then we wouldn't need to do the ListSorter.
Tester
    BOOL_OP = OR
    TEST_CLAUSE = TEST @Value(_ShufflerCT_FeatureCount) >= 0
    TEST_MODE = TEST
    PASSED -> RandomNumberGenerator_2
Note: Pick a random number from 0 to n (where n is originally the number of features) / 26-Jan-2021 / Reduce max value to current loop -1 (because stupid lists run from 0)
RandomNumberGenerator_2
    MAX = @Value(_ShufflerCT_FeatureCount)-1
    MIN = 0
    PLACES = 0
    RESULT_ATTR = _ShufflerCT_SelectedFeature
    -> ListIndexer
    -> AttributeCreator
Note: This is the chosen feature. Send it on.
ListIndexer
    INDEX = @Value(_ShufflerCT_SelectedFeature)
    LIST_ATTR = $(LIST_ATTR)
    -> ListIndexer_Output (output)
ListIndexer_Output (output)
Note: Set the ID for the chosen feature to be -1. / Set n=n-1
AttributeCreator
    ATTR_TABLE:
      SET_TO _ShufflerCT_List{@Value(_ShufflerCT_SelectedFeature)}._ShufflerCT_ID (int64) = -1
      SET_TO _ShufflerCT_FeatureCount (int64) = @Evaluate(@Value(_ShufflerCT_FeatureCount)-1)
    -> ListSorter
Note: Sort list so that chosen features are at the very end. n now represents the last feature not to be yet chosen.
ListSorter
    ORDER = Descending
    SRC_LIST = $(SRC_LIST)
    TYPE = Numeric
    -> FMEFunctionCaller
Note: 26-Jan-2021 / Remove bottom attribute of list. This reduces the amount of work the ListSorter has to do each time. Seems to need to be a function, not an AttributeRemover transformer.
FMEFunctionCaller
    FUNC = @RemoveAttributes(fme_encoded,_ShufflerCT_List{@Value(_ShufflerCT_FeatureCount)}._ShufflerCT_ID)
    -> RandomNumberGenerator_2_Input (output)
Note: Loop back to check if there are items still to be selected
RandomNumberGenerator_2_Input (output)

FME custom transformer FeatureShuffler
Description
This transformer shuffles the order of features in a random way. 
Typical Uses
The transformer's primary use is randomizing the orders of features where a known algorithm is desired. It could be used in workspace testing (for example), to randomize data to ensure a solution works regardless of feature order.
Algorithms
Two algorithms are available:
Naïve Sorting
Naïve Sorting is where each feature is assigned a random number and the data sorted in that order. 
This method is generally much quicker and more suited to large quantities of data. However, it is naïve because its simpler algorithm has potential drawbacks for unbiased ordering. 
For example, we cannot guarantee that two or more features will not receive the same random number, which is problematic because the Sorter transformer will not differentiate between the two and pick by the original order.
Fisher-Yates Shuffle
The Fisher-Yates algorithm is where features are held in a list and picked at random (rnd(n) where n is the length of the list). The selected feature is sorted to the bottom of the list, and n set to n-1, so that it cannot be selected a second time.
This method is generally slower and more suited to smaller quantities of data (I suggest no more than 10,000 features). However, it is better in terms of results because it reorders data with no bias, where each feature is selected with equal probability.
Note: For an absolutely bias-free solution, you should replace the RandomNumberGenerator transformer inside FeatureShufflerLoop, with a TrueRandomIntGenerator transformer from the FME Hub.
The Fisher-Yates shuffle is implemented as a looping custom transformer and is a good example of that technique. By putting the loop in a "sub-transformer" (FeatureShufflerLoop) it avoids trying to loop with a blocking transformer (the Aggregator).
Outputs
Features are output through the Shuffled port, sorted or shuffled into their random order. The <Rejected> port outputs features that have - for whatever reason - caused an error to occur inside the transformer.
Did You Know?
Did you know... a deck of 52 playing cards must be riffle shuffled 8 to 9 times to get a truly random order (3/2 log2 n where n is the number of cards)?!
Keywords: Sort Sorter Shuffle Order Random Loop

Parameters:
- GeneralBox =   # ShuffleType General
- ShuffleType = NS   # Naïve Sorting,NS%Fisher-Yates,FY Algorithm Type

Input (input)
    -> TestFilter
TestFilter
    DEFAULT_VALUE = Fisher-Yates
    PASSED_TEST_GROUP_OUTPUT = FIRST
    TEST_LIST = "BOOL_OP,OR,COMPOSITE_TEST,""""""1"""""",TEST_CLAUSE,TEST $(ShuffleType) = NS",Naïve Sorting
    Naïve Sorting -> RandomNumberGenerator
    Fisher-Yates -> Counter

Bookmark: Naive Sort
Note: Select a random number from 0-2³² because why not.
RandomNumberGenerator
    MAX = 4294967296
    MIN = 0
    PLACES = 0
    RESULT_ATTR = _ShufflerCT_SortOrder
    -> Sorter
Note: Rejected
Junction
    -> Junction_2

Bookmark: Fisher-Yates Shuffle
Note: Give each feature an ID number
Counter
    CNT_ATTR = _ShufflerCT_ID
    SCOPE = Local
    START = 0
    -> Aggregator
    -> FeatureMerger [REQUESTOR]
Note: Create a list of the feature ID numbers
Aggregator
    ACCUM_ATTRS_NAME = Drop Incoming Attributes
    LIST_ATTRS_TO_INCLUDE = _ShufflerCT_ID
    LIST_NAME = _ShufflerCT_List
    MODE = Attributes Only
    SEP = ,
    AGGREGATE -> ListElementCounter
Note: Count how many elements are in the list (i.e. how many features there are)
Note: FeatureShuffler by Mark Ireland / (c) Safe Software Inc / mark.ireland@safe.com
ListElementCounter
    CNT_ATTR = _ShufflerCT_FeatureCount
    LIST_NAME = _ShufflerCT_List{}
    -> FeatureShufflerLoop [RandomNumberGenerator_2_Input]
Note: Select features randomly
FeatureShufflerLoop
    LIST_ATTR = _ShufflerCT_List{}
    SRC_LIST = _ShufflerCT_List{}._ShufflerCT_ID
    _SHUFFLERCT_FEATURECOUNT = @Value(_ShufflerCT_FeatureCount)
    ListIndexer_Output -> Counter_2
Note: Create an attribute containing the sort order that can be passed back to the original feature.
Counter_2
    CNT_ATTR = _ShufflerCT_SortOrder
    SCOPE = Local
    START = 0
    -> FeatureMerger [SUPPLIER]
Note: Pass the sort order attribute back to the original feature
FeatureMerger
    ATTR_ACCUM_MODE = Merge Supplier
    ATTR_CONFLICT_RES_LOOKUP = REQUESTOR_IF_CONFLICT
    IGNORE_NULLS = No
    JOIN_KEYS = @Value(_ShufflerCT_ID) @Value(_ShufflerCT_ID) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> Sorter

Bookmark: Sort Data and Do Cleanup
Note: Sort the data in its new order
Sorter
    SORT_PARM = _ShufflerCT_SortOrder NUMERIC ASCENDING
    SORTED -> BulkAttributeRemover
Note: Clean up used attributes
BulkAttributeRemover
    ATTR_EXP = _ShufflerCT
    -> Shuffled (output)

Bookmark: Outputs
Shuffled (output)
Note: Rejections
Junction_2
    -> AttributeCreator
AttributeCreator
    ATTR_TABLE = SET_TO fme_rejection_code (varchar(200)) = UNKNOWN_ERROR
    -> <Rejected> (output)
<Rejected> (output)
