FME workspace dog-api_parte2.fmw
Title: API: Dados e Resultados | Simplificando a interface com APIs com solução ETL FME Form
History: 14/11/2024,Thiago Brigagão,Criação do fluxo

Parameters:
- PARAMETER =   # Parâmetros de Entrada
- param_api = https://api.thedogapi.com/v1   # https API
- param_token =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   # Token
- param_fotos = D:\gitHub\SolutialTech\2025\01\API-part2\1-dataset\Fotos   # INCLUDE_WEB_BROWSER Path Fotos

Readers:
- PATH_1: PATH from $(param_fotos)

Note: ATENÇÃO / Incluir o Token para o correto funcionamento do fluxo. / PRIMEIROS PASSOS / A API atualmente funciona sem o Token, porém, o resultado retornado é diferente. Mesmo sem o token ela funcionará, mas o fluxo a seguir foi desenvolvido com a API para aumentar o número de retornos da primeira página.
Note: COMO GERAR O TOKEN / Acessar o DOG API e criar um TOKEN de acesso para você em https://thedogapi.com/signup / Você receberá o token por e-mail. Acessar o e-mail e incluir o token nos parâmetros do FME / DOCUMENTAÇÃO / The Dog API - Documentação

Bookmark: 1.0 | Start do Fluxo
Creator
    GEOMTYPE = Geometry Object
    NUM = 1
    CREATED -> HTTPCaller_5

Bookmark: 2.1 | GET para Recuperar os MEUS UPLOADs (IMAGENS)
Note: API / https://api.thedogapi.com/v1/images / Method / GET / Hearders / Content-Type: application/json / x-api-key: <seu TOKEN da Dog API> / QueryString / limit / [Optional] number of images to return valid 1 to 10 - default: 1 / page / [Optional] only works if account_id is present to page through your own uploads / order / [Optional] only works if account_id is present, either ASC or DESC - ascending or descending. / sub_id / [Optional] If you want to / breed_ids / [Optional] Id's of the breeds to filter by / category_ids / [Optional] Id's of the categories to filter by / format / [Optional] default is 'json', pass 'src' to redirect the request to the image's url - this is useful for setting the 'src' of an tag. / original_filename / [Optional] filter to files you uploaded with the same name
HTTPCaller_5
    CLIENT_CERTIFICATE_TYPE = NONE
    CONNECTION_TIMEOUT_LENGTH = 60
    CUSTOM_HEADERS = x-api-key;$(param_token)
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(param_api)/images?limit=10
    TEST_DIALOG_ATTRIBUTE = token;live_zFoc6yCV8x3ixTyDaMhf6tL8SRkvJll5T5er2wqYgtll6IVVcT2zrlZTMNYhJDig
    TEST_DIALOG_PARAMETERS_FOR_RESPONSE = authConnection;<Unused> authEnabled;false authMethod;<Unused> authPassword;<Unused> authUsername;<Unused> contentType;<Unused> method;GET multipartContentType;<Unused> requestHeaders:Content-Type;application/json requestHeaders:x-api-key;live_zFoc6yCV8x3ixTyDaMhf6tL8SRkvJll5T5er2wqYgtll6IVVcT2zrlZTMNYhJDig requestUrl;https://api.thedogapi.com/v1/images/search?size=small&mime_types=jpg&format=json&has_breeds=true&order=RANDOM&page=0&limit=25 uploadData;<Unused> verifySslCert;Yes version;HTTP_2
    TEST_DIALOG_RESPONSE_PREVIEW =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
    TEST_DIALOG_RESPONSE_STATUS:
      HTTP/2 200
      Download Size: 15287 bytes
      Total Transfer Time: 6981 ms
    TRANSFER_TIMEOUT_LENGTH = 90
    USE_COOKIES = No
    VERIFY_SSL_CERTIFICATES = Yes
    -> JSONFragmenter_2

Bookmark: 2.2 | Fragmentando o Json para recuperar a URL
Note: [ / { / "breeds":[ / ], / "id":"neHp6EZ95", / "url":"https://cdn2.thedogapi.com/images/neHp6EZ95.jpg", / "width":400, / "height":400, / "sub_id":null, / "created_at":"2025-01-03T18:14:55.000Z", / "original_filename":"border-collie-tn.jpg", / "breed_ids":null / }, / { / "breeds":[ / ], / "id":"Xandps7DO", / "url":"https://cdn2.thedogapi.com/images/Xandps7DO.jpg", / "width":400, / "height":400, / "sub_id":null, / "created_at":"2025-01-03T18:14:13.000Z", / "original_filename":"border-collie-tn.jpg", / "breed_ids":null / }, / { / ...... / } / ]
Note: Para a extração da URL precisamos verificar os atributos que estão na raiz de retorno, sendo assim usamos o json[*] para extrair os atributos em negrito
JSONFragmenter_2
    EXPLODE_FORMAT = JSON
    EXTRACT_ATTR = Yes
    JSON_ATTR = _response_body
    JSON_QUERY = json[*]
    NEW_ATTRIBUTES = id buffer url buffer width buffer height buffer sub_id buffer created_at buffer original_filename buffer breed_ids buffer
    READ_FROM_FILE = NO
    RECURSIVE = YES
    REJECT_EMPTY_LISTS = YES
    FRAGMENTS -> AttributeManager_3
Note: AttributeManager_3 [AttributeManager Version 5] / Attribute Actions: / Input Attribute / Output Attribute / Value / Type / Action / _creation_instance / _creation_instance / uint64 / Remove / _response_body / _response_body / buffer / Remove / _http_status_code / _http_status_code / buffer / Remove / json_type / json_type / buffer / Remove / json_index / json_index / uint32 / Remove
AttributeManager_3
    ATTR_TABLE:
      REMOVE _creation_instance (uint64)
      REMOVE _response_body (buffer)
      REMOVE _http_status_code (buffer)
      REMOVE json_type (buffer)
      REMOVE json_index (uint32)
    -> HTTPCaller_7 [off]

Bookmark: 3.1 | DELETE de TODAS as Imagens Retornadas pelo GET
Note: API / https://api.thedogapi.com/v1/images/:image_id / Method / DELETE / Hearders / x-api-key: <seu TOKEN da Dog API>
HTTPCaller_7 [off]
    CLIENT_CERTIFICATE_TYPE = NONE
    CONNECTION_TIMEOUT_LENGTH = 60
    CONTENT_TYPE_LOOKUP = application/json
    CUSTOM_HEADERS = x-api-key;$(param_token)
    ERROR_ATTR = _error
    FOLLOW_REDIRECTS = FOLLOW_WITH_GET
    HTTP_METHOD = DELETE
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(param_api)/images/@Value(id)
    TRANSFER_TIMEOUT_LENGTH = 90
    UPLOAD_TYPE = STRING_UPLOAD
    USE_COOKIES = No
    VERIFY_SSL_CERTIFICATES = Yes
    UPLOAD_CONTENT_TYPE = JSON (application/json)

Bookmark: 1.0 | Leitura do PATHS com TODAS as Imagens
Note: Leitura do diretório com as fotos do Dog's
PATH (reader PATH_1) [off]
    attributes: path_unix buffer, path_windows buffer, path_rootname buffer, path_filename buffer, path_extension buffer, path_directory_unix buffer, path_directory_windows buffer, path_type char(10)
    -> HTTPCaller_3

Bookmark: 4.1 | POST para Enviar as IMAGENS para a API
Note: API / https://api.thedogapi.com/v1/images/upload / Method / POST / Hearders / x-api-key: <seu TOKEN da Dog API> / Body / Multipart / Form Data / Multipart Upload / file: Arquivo que será enviado no POST / sub_id: Identificador
HTTPCaller_3
    CLIENT_CERTIFICATE_TYPE = NONE
    CONNECTION_TIMEOUT_LENGTH = 60
    CUSTOM_HEADERS = x-api-key;$(param_token)
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    MULTIPARTS = file FileUpload SOURCE_FILE;@Value(path_windows);MIME_TYPE;image/jpeg;FME_CONTROLLER_QUERY_FILE;transformers/dependencies/http/FileUpload.fme;FME_CONTROLLER_CHOICE;FileUpload sub_id StringUpload SOURCE_EXPRESSION;solutial;MIME_TYPE;text/plain;FME_CONTROLLER_QUERY_FILE;transformers/dependencies/http/StringUpload.fme;FME_CONTROLLER_CHOICE;StringUpload
    MULTIPART_CONTENT_TYPE = FORM_DATA
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(param_api)/images/upload
    TEST_DIALOG_ATTRIBUTE = token;live_zFoc6yCV8x3ixTyDaMhf6tL8SRkvJll5T5er2wqYgtll6IVVcT2zrlZTMNYhJDig
    TEST_DIALOG_PARAMETERS_FOR_RESPONSE = authConnection;<Unused> authEnabled;false authMethod;<Unused> authPassword;<Unused> authUsername;<Unused> contentType;<Unused> method;GET multipartContentType;<Unused> requestHeaders:Content-Type;application/json requestHeaders:x-api-key;live_zFoc6yCV8x3ixTyDaMhf6tL8SRkvJll5T5er2wqYgtll6IVVcT2zrlZTMNYhJDig requestUrl;https://api.thedogapi.com/v1/images/search?size=small&mime_types=jpg&format=json&has_breeds=true&order=RANDOM&page=0&limit=25 uploadData;<Unused> verifySslCert;Yes version;HTTP_2
    TEST_DIALOG_RESPONSE_PREVIEW =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
    TEST_DIALOG_RESPONSE_STATUS:
      HTTP/2 200
      Download Size: 15287 bytes
      Total Transfer Time: 6981 ms
    TRANSFER_TIMEOUT_LENGTH = 90
    UPLOAD_TYPE = MULTIPART_UPLOAD
    USE_COOKIES = No
    VERIFY_SSL_CERTIFICATES = Yes
    -> JSONFlattener

Bookmark: 4.2 | Fragmentando o Json para recuperar a URL
Note: JSONFlattener [JSONFlattener Version 7] / Source: / Input Source: JSON Document / JSON Document: @Value(_response_body) / Flattening: / Recursively Flatten Objects/Arrays: Yes / Prefix New Attribute Names With: <not set> / Attributes to Expose: id url width height original_filename pending / Output Attribute Name: / List Attribute for JSON Parsing Errors: _json_error
JSONFlattener
    ERROR_LIST_ATTR = _json_error
    JSON_DOCUMENT = @Value(_response_body)
    NEW_ATTRIBUTES = id buffer url buffer width buffer height buffer original_filename buffer pending buffer
    READ_FROM_FILE = NO
    RECURSIVE = YES
    -> AttributeManager
Note: AttributeManager [AttributeManager Version 5] / Attribute Actions: Input AttributeOutput AttributeValueTypeActionpath_windowspath_windowsbufferRemovepath_filenamepath_filenamebufferRemovepath_extensionpath_extensionbufferRemove_http_status_code_http_status_codebufferRemove
AttributeManager
    ATTR_TABLE:
      REMOVE path_windows (buffer)
      REMOVE path_filename (buffer)
      REMOVE path_extension (buffer)
      REMOVE _http_status_code (buffer)
    -> RandomNumberGenerator [off]

Bookmark: PLUS > Fazendo mais um POST de Exemplo
Note: Gera valores de votação randômicos
RandomNumberGenerator [off]
    MAX = 20
    MIN = 1
    PLACES = 0
    RESULT_ATTR = _random_number
    -> HTTPCaller_2 [off]
Note: Faz um post de votação para as imagens dos Dog's que fizemos upload anteriormente
HTTPCaller_2 [off]
    CLIENT_CERTIFICATE_TYPE = NONE
    CONNECTION_TIMEOUT_LENGTH = 60
    CONTENT_TYPE_LOOKUP = application/json
    CUSTOM_HEADERS = x-api-key;$(param_token)
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(param_api)/votes
    TRANSFER_TIMEOUT_LENGTH = 90
    UPLOAD_BODY:
      {
      	"image_id":"@Value(id)",
      	"sub_id": "solutial",
      	"value":@Value(_random_number)
      }
    UPLOAD_TYPE = STRING_UPLOAD
    USE_COOKIES = No
    VERIFY_SSL_CERTIFICATES = Yes
    UPLOAD_CONTENT_TYPE = JSON (application/json)
